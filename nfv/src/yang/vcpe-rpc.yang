module vcpe-rpc{
    namespace "http://com/singtel/vcpe";
    prefix vcpe;

    import ietf-inet-types {
        prefix inet;
    }
    import tailf-common {
        prefix tailf;
    }
    import sites {
        prefix sites;
    }
    import nfv-types { 
        prefix nfvt; 
    }

    organization "Cisco";

    contact
    "Joe L. User ACME, Inc. 42 Anywhere Drive Nowhere, CA 95134 USA
    Phone: +1 800 555 0100 EMail: joe@acme.example.com";

    description
    "vcpe service creation";

    reference "nfv.yang";

    /* 
    vcpe rpc create call
    */  


    rpc create-vcpe {
        tailf:info "create vcpe service";
        tailf:actionpoint vcpe-create;

        input {
            // description "vcpe RFS service creation action inputs”;    	

            leaf service-name {
                tailf:info "Name of the vcpe service";
                mandatory true;
                type string {
                    length "1..20";
                }
            }

            leaf access-service-type {
                tailf:info "Access service type";
                type enumeration {
                    enum megapop {
                        tailf:info "Singtel Megapop service";
                    }
                    enum cplus {
                        tailf:info "Singtel CPlus service";
                    }
                    enum singnet {
                        tailf:info "Singtel SingNet service";
                    }
                }
                default megapop;
            }

            leaf brn {
                tailf:info "Business Registration Number in Pegasus";
                type string;
            }
            leaf ban {
                mandatory true;
                tailf:info "Billing Account Number in Pegasus";
                type string;
            }
            leaf sid {
                tailf:info "Service Identifier";
                type string;
            }
            leaf lan-ip {
                tailf:info "LAN IP Address";
                mandatory true;
                type tailf:ipv4-address-and-prefix-length;
            }
            leaf wan-ip {
                tailf:info "WAN IP Address";
                mandatory true;
                type tailf:ipv4-address-and-prefix-length;
            }
            leaf routing-protocol {
                tailf:info "Routing Protocol";
                mandatory true;
                type enumeration {
                    enum static {
                        tailf:info "Static routing mode";
                    }
                    enum bgp {
                        tailf:info "BGP mode";
                    }
                }
            }
            leaf gateway {
                tailf:info "Gateway Address for Static Routing";
                type inet:ipv4-address;
            }
            leaf as-number {
                tailf:info "BGP AS Number";
                when "../routing-protocol='bgp'" {
                    tailf:dependency ".";
                    tailf:dependency "../routing-protocol";
                }
                type uint32;
            }
            leaf remote-as-number {
                tailf:info "REMOTE AS Number";
                when "../routing-protocol='bgp'" {
                    tailf:dependency ".";
                    tailf:dependency "../routing-protocol";
                }
                type uint32;
            }
            leaf neighbor-passwd {
                tailf:info "REMOTE AS Number";
                when "../routing-protocol='bgp'" {
                    tailf:dependency ".";
                    tailf:dependency "../routing-protocol";
                }
                type string;
            }
            leaf site-code {
                tailf:info "Site Code";
                mandatory true;
                type leafref {
                    path "/sites:sites/sites:site/sites:site-code";
                }
            }
            leaf pod {
                when "../site-code";
                type leafref {
                    path "/sites:sites/sites:site[sites:site-code=current()/../site-code]/"+
                    "sites:pods/sites:pod/sites:pod-name";
                }
            }
            leaf dci {
                when "../pod";
                type leafref {
                    path "/sites:sites/sites:site[sites:site-code=current()/../site-code]/"+
                    "sites:pods/sites:pod[sites:pod-name=current()/../pod]/"+
                    "sites:dci/sites:dci-name";
                }
            }
            leaf dci-link-end-point {
                when "../dci";
                type leafref {
                    path "/sites:sites/sites:site[sites:site-code=current()/../site-code]/"+
                        "sites:pods/sites:pod[sites:pod-name=current()/../pod]/"+
                        "sites:dci[sites:dci-name=current()/../dci]/"+
                        "sites:dci-link/sites:link-end-point-id";
                }
            }

            leaf ingress-id{
                tailf:info "Ingress VLAN Id";               
                type uint32;
            }
            leaf egress-id{
                tailf:info "Egress VLAN Id";               
                type uint32;
            }
            leaf ingress-mac-address
            {
                type nfvt:mac-address{
                    tailf:info "MAC address for ingress";	
                }
            }
            leaf egress-mac-address
            {
                type nfvt:mac-address{
                    tailf:info "MAC address for egress";	
                }
            }

            list lan-cvlans {
                tailf:info "Ingress VLAN subinterfaces";
                key "lan-cvlan-id";
                leaf lan-cvlan-id {
                    tailf:info "LAN subinterface id";
                    type uint32;                    
                }
                leaf lan-cvlan-ip {
                    tailf:info "LAN subinterface IP Address";
                    type tailf:ipv4-address-and-prefix-length;
                }                     
            } 
            list wan-cvlans {
                tailf:info "Egress VLAN subinterfaces";
                key "wan-cvlan-id";
                leaf wan-cvlan-id {
                    tailf:info "WAN subinterface id";
                    type uint32;                    
                }
                leaf wan-cvlan-ip {
                    tailf:info "WAN subinterface IP Address";
                    type tailf:ipv4-address-and-prefix-length;
                }
            }

            leaf nfv-vas-reference {
                tailf:info "nfv vas reference";
                type string;
                mandatory true;
            }
            leaf product-code
            {
                tailf:info "product code";
                type string;
                mandatory true;
            }

            leaf nfv-vas-scheme {
                tailf:info "nfv vas scheme";
                type enumeration {
                    enum basic {
                        tailf:info "basic";
                    }
                    enum advanced {
                        tailf:info "advanced";
                    }
                    enum premium {
                        tailf:info "premium";
                    }					
                }
                mandatory true;
            }
            leaf brand
            {
                tailf:info "Brand name";
                type enumeration {
                    enum cisco {
                        tailf:info "cisco";
                    }
                    enum fortigate {
                        tailf:info "fortigate";
                    }

                }
                mandatory true;
            }
            leaf nfv-setup
            {
                tailf:info "NFV setup name";
                type enumeration {
                    enum hosted {
                        tailf:info "hosted";
                    }
                    enum edge {
                        tailf:info "edge";
                    }
                    enum branch {
                        tailf:info "branch";
                    }

                }
                mandatory true;
            }
            leaf nfv-access-setup
            {
                tailf:info "NFV access setup name";
                type enumeration {
                    enum l2nid {
                        tailf:info "l2nid";
                    }
                    enum l3nid {
                        tailf:info "l3nid";
                    }
                    enum l3vpn {
                        tailf:info "l2vpn";
                    }
                }
                mandatory true;
            }

            leaf circuit-reference
            {
                tailf:info "circuit reference";
                type string;
                mandatory true;
            }
            leaf speed
            {
                tailf:info "Speed value";
                type string;
                mandatory true;
            }

        }

        output {
                leaf result {
                    type enumeration {
                    enum ok;
                    enum nok;
                    }
                }
                leaf hostname {
                    type string;
                }
                leaf ingress-id{
                    tailf:info "Ingress VLAN Id"; 
                    type uint32;
                }
                leaf egress-id{
                    tailf:info "Egress VLAN Id";
                    type uint32;
                }
                leaf management-ip {
                    tailf:info "Management ip of csr1kv";
                    type inet:ipv4-address;
                }
                leaf errno {
                    type enumeration {
                        enum no-such-site;
                        enum no-such-pod;
                        enum no-such-dci;
                        enum no-such-link-endpoint;
                        enum no-such-link-endpoint-service-type;
                        enum vlan-id-exhausted;
                        enum mgmt-ip-exhausted;
                        enum unexpected-error;
                    }
                }
            }
    }

    /* 
    vcpe modify call
    */ 

    rpc modify-vcpe {
        tailf:info "modify vcpe service";
        tailf:actionpoint vcpe-modify;

        input {
            //    description "vcpe RFS service instance modification”;
            leaf service-name {
                tailf:info "Name of the vcpe service";
                type string {
                    length "1..20";
                }
                mandatory true;
            }
            leaf access-service-type {
                tailf:info "Access service type";
                type enumeration {
                    enum megapop {
                        tailf:info "Singtel Megapop service";
                    }
                    enum cplus {
                        tailf:info "Singtel CPlus service";
                    }
                    enum singnet {
                        tailf:info "Singtel SingNet service";
                    }
                }
                default megapop;
            }
            leaf sid {
                tailf:info "Service Identifier";
                type string;
            }
            leaf lan-ip {
                tailf:info "LAN IP Address";
                type tailf:ipv4-address-and-prefix-length;
            }
            leaf wan-ip {
                tailf:info "WAN IP Address";
                type tailf:ipv4-address-and-prefix-length;
            } 

            leaf routing-protocol {
                tailf:info "Routing Protocol";
                type enumeration {
                    enum static {
                        tailf:info "Static routing mode";
                    }
                    enum bgp {
                        tailf:info "BGP mode";
                    }
                }
            }
            leaf gateway {
                tailf:info "Gateway Address for Static Routing";
                type inet:ipv4-address;
            }
            leaf as-number {
                tailf:info "BGP AS Number";
                when "../routing-protocol='bgp'" {
                    tailf:dependency ".";
                    tailf:dependency "../routing-protocol";
                }
                type uint32;
            }
            leaf remote-as-number {
                tailf:info "REMOTE AS Number";
                when "../routing-protocol='bgp'" {
                    tailf:dependency ".";
                    tailf:dependency "../routing-protocol";
                }
                type uint32;
            }
            leaf neighbor-passwd {
                tailf:info "REMOTE AS Number";
                when "../routing-protocol='bgp'" {
                    tailf:dependency ".";
                    tailf:dependency "../routing-protocol";
                }
                type string;
            }

        }

        output {
                leaf result {
                    type enumeration {
                    enum ok;
                    enum nok;
                    }
                }
                leaf success-message {
                    type string;
                }
                leaf errno {
                    type enumeration {
                        enum unexpected-error;
                    }
                }
            }
    }

    /* 
    vcpe delete call
    */ 

    rpc delete-vcpe {
        tailf:info "delete vcpe service";
        tailf:actionpoint vcpe-delete;

        input {
            //   description "vcpe RFS service instance deletion”;
            leaf service-name {
                tailf:info "Name of the vcpe service";
                type string {
                    length "1..20";
                }
                mandatory true;
            }
        }

        output {
                leaf result {
                    type enumeration {
                    enum ok;
                    enum nok;
                    }
                }
                leaf success-message {
                    type string;
                }
                leaf errno {
                    type enumeration {
                        enum unexpected-error;
                    }
                }
            }
    }

    rpc create-vcpe-subinterfaces {
        tailf:info "create vcpe subinterfaces";
        tailf:actionpoint create-vcpe-subinterfaces;

        input {
            // description "vcpe RFS subinterfaces creation;
            leaf service-name {
                tailf:info "Name of the vcpe service";
                type string {
                    length "1..20";
                }
                mandatory true;
            }
            list lan-cvlans {
                tailf:info "Ingress VLAN subinterfaces";
                key "lan-cvlan-id";
                leaf lan-cvlan-id {
                    tailf:info "LAN subinterface id";
                    type uint32;                    
                }
                leaf lan-cvlan-ip {
                    tailf:info "LAN subinterface IP Address";
                    type tailf:ipv4-address-and-prefix-length;
                }                     
            } 
            list wan-cvlans {
                tailf:info "Egress VLAN subinterfaces";
                key "wan-cvlan-id";
                leaf wan-cvlan-id {
                    tailf:info "WAN subinterface id";
                    type uint32;                    
                }
                leaf wan-cvlan-ip {
                    tailf:info "WAN subinterface IP Address";
                    type tailf:ipv4-address-and-prefix-length;
                }                     
            }
        }

        output {
                leaf result {
                    type enumeration {
                    enum ok;
                    enum nok;
                    }
                }
                leaf success-message {
                    type string;
                }
                leaf errno {
                    type enumeration {
                        enum unexpected-error;
                    }
                }
            }
    }

    rpc delete-vcpe-subinterface {
        tailf:info "deletion of vcpe subinterface";
        tailf:actionpoint delete-vcpe-subinterface;

        input {
            // description "vcpe RFS subinterface deletion;
            leaf service-name {
                tailf:info "Name of the vcpe service";
                type string {
                    length "1..20";
                }
                mandatory true;
            }
            leaf lan-cvlan-id {
                tailf:info "LAN subinterface id to delete";
                type uint32;                    
            }
            leaf wan-cvlan-id {
                tailf:info "WAN subinterface id to delete";
                type uint32;                    
            }
        }

        output {
                leaf result {
                    type enumeration {
                    enum ok;
                    enum nok;
                    }
                }
                leaf success-message {
                    type string;
                }
                leaf errno {
                    type enumeration {
                        enum unexpected-error;
                    }
                }
            }
    }
}
